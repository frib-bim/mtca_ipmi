head 1.1;
branch ;
access ;
symbols ;
locks ; strict;
comment @@;


1.1
date 2014.09.02.14.30.37; author anton; state Engineering;
branches ;
next ;

ext
@project //Natone/natsrc/tcpip_lwip/doc/mibs/nmch_mib.pj;
@

desc
@@


1.1
log
@Initial revision@
text
@--********************************************************************************
--*
--* Name                :     PetEvents.mib
--* Description         :     MIB file for Platform Event Traps events
--* Created             :     February 5, 2004
--* Author              :     Intel Corporation
--* Revision            :     1.0
--*
--*
--* Copyright (c) 2004 Intel Corporation. All Rights Reserved. 
--********************************************************************************


PET-EVENTS DEFINITIONS ::= BEGIN

	IMPORTS
		enterprises
			FROM RFC1155-SMI
		OBJECT-TYPE
			FROM RFC-1212

        	TRAP-TYPE
		        FROM RFC-1215
  

		DisplayString
			FROM RFC1213-MIB;

	wiredformgmt     OBJECT IDENTIFIER ::= { enterprises 3183 }
	pet              OBJECT IDENTIFIER ::= { wiredformgmt 1 }

-- MODULE IDENTIFICATION
--
--  PET Events Alerting MODULE-IDENTITY
--  LAST-UPDATED "February 4, 2004"
--  ORGANIZATION "Intel Corporation"
--  CONTACT-INFO
--   " PET Events,
--     Intel Corporation, DP3-407
--	   DuPont, WA 98352"
--  DESCRIPTION
--  "This is the MIB file for SNMPv1.0 based PET traps"


-- ****************************************
-- SYSTEM INFORMATION BRANCH STARTS HERE.
-- ****************************************

petEvts 		OBJECT IDENTIFIER ::= { pet 1 }


-- **********************************************
-- *		Temperature			*
-- **********************************************

-- Lower Non Critical threshold crossed
 petTrapUnderTemperatureWarning TRAP-TYPE
 ENTERPRISE petEvts
 DESCRIPTION 
 "Under-Temperature Warning (Lower non-critical, going low)"

--#TYPE       "Temperature Event"
--#SUMMARY    "Under-Temperature Warning (Lower non-critical, going low)"
--#ARGUMENTS  {}
--#SEVERITY   WARNING

 ::= 65792



-- Lower Non Critical threshold crossed
petTrapUnderTemperatureWarningGH TRAP-TYPE
ENTERPRISE petEvts
DESCRIPTION 
"Under-Temperature Warning (Lower Non-Critical - going high)"

--#TYPE       "Temperature Event"
--#SUMMARY    "Under-Temperature Warning (Lower non-critical, going high)"
--#ARGUMENTS  {}
--#SEVERITY   WARNING

::= 65793



-- Lower Critical threshold crossed
petTrapUnderTemperatureCritical TRAP-TYPE
ENTERPRISE petEvts
DESCRIPTION 
"Critical Under-Temperature Problem (Lower Critical - going low)"

--#TYPE       "Temperature Event"
--#SUMMARY    "Critical Under-Temperature Problem (Lower Critical - going low)"
--#ARGUMENTS  {}
--#SEVERITY   CRITICAL

 ::= 65794



-- Lower Critical threshold crossed
 petTrapUnderTemperatureCriticalGH TRAP-TYPE
 ENTERPRISE petEvts
 DESCRIPTION 
 "Critical Under-Temperature Problem (Lower Critical - going high)"

--#TYPE       "Temperature Event"
--#SUMMARY    "Critical Under-Temperature Problem (Lower Critical - going high)"
--#ARGUMENTS  {}
--#SEVERITY   CRITICAL

::= 65795



-- Lower Critical threshold crossed
petTrapUnderTemperatureNonRecoverableGL TRAP-TYPE
ENTERPRISE petEvts
DESCRIPTION 
"Non-recoverable Under-Temperature Problem (Lower Non-recoverable - going low)"

--#TYPE       "Temperature Event"
--#SUMMARY    "Non-recoverable Under-Temperature Problem (Lower Non-recoverable - going low)"
--#ARGUMENTS  {}
--#SEVERITY   CRITICAL

 ::= 65796



-- Lower Critical threshold crossed
 petTrapUnderTemperatureNonRecoverableGH TRAP-TYPE
 ENTERPRISE petEvts
 DESCRIPTION 
 "Non-recoverable Under-Temperature Problem (Lower Non-recoverable - going high)"

--#TYPE       "Temperature Event"
--#SUMMARY    "Non-recoverable Under-Temperature Problem (Lower Non-recoverable - going high)"
--#ARGUMENTS  {}
--#SEVERITY   CRITICAL

::= 65797



-- Upper Non Critical threshold crossed
 petTrapOverTemperatureWarningGL TRAP-TYPE
 ENTERPRISE petEvts
 DESCRIPTION 
 "Over-Temperature Warning (Upper non-critical, going low)"

 --#TYPE       "Temperature Event"
 --#SUMMARY    "Over-Temperature Warning (Upper non-critical, going low)"
 --#ARGUMENTS  {}
 --#SEVERITY   WARNING

 ::= 65798



-- Upper Non Critical threshold crossed
 petTrapOverTemperatureWarning TRAP-TYPE
 ENTERPRISE petEvts
 DESCRIPTION 
 "Over-Temperature Warning (Upper non-critical, going high)"

 --#TYPE       "Temperature Event"
 --#SUMMARY    "Over-Temperature Warning (Upper non-critical, going high)"
 --#ARGUMENTS  {}
 --#SEVERITY   WARNING

 ::= 65799



-- Upper Critical threshold crossed
 petTrapOverTemperatureCriticalGL TRAP-TYPE
 ENTERPRISE petEvts
 DESCRIPTION 
 "Critical Over-Temperature Problem (Upper Critical - going low)"

 --#TYPE       "Temperature Event"
 --#SUMMARY    "Critical Over-Temperature Problem (Upper Critical - going low)"
 --#ARGUMENTS  {}
 --#SEVERITY   CRITICAL

 ::= 65800



-- Upper Critical threshold crossed
 petTrapOverTemperatureCritical TRAP-TYPE
 ENTERPRISE petEvts
 DESCRIPTION 
 "Critical Over-Temperature Problem (Upper Critical - going high)"

--#TYPE       "Temperature Event"
--#SUMMARY    "Critical Over-Temperature Problem (Upper Critical - going high)"
--#ARGUMENTS  {}
--#SEVERITY   CRITICAL

 ::= 65801




-- Upper Critical threshold crossed
 petTrapOverTemperatureNonRecoverableGL TRAP-TYPE
 ENTERPRISE petEvts
 DESCRIPTION 
 "Non-recoverable Over-Temperature Problem (Upper Non-recoverable - going low)"

 --#TYPE       "Temperature Event"
 --#SUMMARY    "Non-recoverable Over-Temperature Problem (Upper Non-recoverable - going low)"
 --#ARGUMENTS  {}
 --#SEVERITY   CRITICAL

 ::= 65802



-- Upper Critical threshold crossed
 petTrapOverTemperatureNonRecoverableGH TRAP-TYPE
 ENTERPRISE petEvts
 DESCRIPTION 
 "Non-recoverable Over-Temperature Problem (Upper Non-recoverable - going high)"

--#TYPE       "Temperature Event"
--#SUMMARY    ""Non-recoverable Over-Temperature Problem (Upper Non-recoverable - going high)"
--#ARGUMENTS  {}
--#SEVERITY   CRITICAL

 ::= 65803




-- Generic critical temperature problem
petTrapGenericCriticalTemperature TRAP-TYPE
ENTERPRISE petEvts
DESCRIPTION 
"Generic Critical Temperature Problem (Transition to Critical from less severe)"

--#TYPE       "Temperature Event"
--#SUMMARY    "Generic Critical Temperature Problem (Transition to Critical from less severe)"
--#ARGUMENTS  {}
--#SEVERITY   CRITICAL

 ::= 67330

-- Generic temperature warning
petTrapGenericTemperatureWarning TRAP-TYPE
ENTERPRISE petEvts
DESCRIPTION 
 "Generic Temperature Warning (Transition to Warning from less severe)"

--#TYPE	      "Temperature Event"
--#SUMMARY    "Generic Temperature Warning (Transition to Warning from less severe)"
--#ARGUMENTS  {}
--#SEVERITY   WARNING

 ::= 67331


-- **********************************************
-- *		Voltage				*
-- **********************************************

-- (Analog voltage) Lower Critical threshold crossed
petTrapUnderAnalogVoltageCritical TRAP-TYPE
ENTERPRISE petEvts
DESCRIPTION 
 "Critical Under-Voltage Problem (Lower Critical - going low)"

--#TYPE       "Voltage Event"
--#SUMMARY    "Critical Under-Voltage Problem (Lower Critical - going low)"
--#ARGUMENTS  {}
--#SEVERITY   CRITICAL

 ::= 131330

-- (Analog voltage) Upper Critical threshold crossed
petTrapOverAnalogVoltageCritical TRAP-TYPE
ENTERPRISE petEvts
DESCRIPTION 
 "Critical Over-Voltage Problem (Upper Critical - going high)"

--#TYPE       "Voltage Event"
--#SUMMARY    "Critical Over-Voltage Problem (Upper Critical - going high)"
--#ARGUMENTS  {}
--#SEVERITY   CRITICAL

 ::= 131337

-- (Discrete voltage) Critical voltage problem
petTrapGenericCriticalDiscreteVoltage2 TRAP-TYPE
ENTERPRISE petEvts
DESCRIPTION 
 "Generic Critical Voltage Problem (Transition to Critical from less severe)"

--#TYPE	      "Voltage Event"
--#SUMMARY    "Generic Critical Voltage Problem (Transition to Critical from less severe)"
--#ARGUMENTS  {}
--#SEVERITY   CRITICAL

 ::= 132866

-- (Discrete voltage) Non-Critical voltage problem
petTrapGenericDiscreteVoltageWarning TRAP-TYPE
ENTERPRISE petEvts
DESCRIPTION 
 "Generic Voltage Warning (Transition to Non-Critical from less severe)"

--#TYPE	      "Voltage Event"
--#SUMMARY    "Generic Voltage Warning (Transition to Non-Critical from less severe)"
--#ARGUMENTS  {}
--#SEVERITY   WARNING

 ::= 132867


-- **********************************************
-- *			Fan			*
-- **********************************************

 petTrapGenericCriticalFan TRAP-TYPE
 ENTERPRISE petEvts
 DESCRIPTION 
  "Generic Critical Fan failure (Transition to Critical from less severe)"

--#TYPE	"FAN Event"
--#SUMMARY    "Generic Critical Fan failure (Transition to Critical from less severe)"
--#ARGUMENTS  {}
--#SEVERITY   CRITICAL

 ::= 263938


 petTrapGenericFanWarning TRAP-TYPE
 ENTERPRISE petEvts
 DESCRIPTION 
  "Generic Predictive Fan failure (predictive failure asserted)"

--#TYPE	"FAN Event"
--#SUMMARY    "Generic Predictive Fan failure (predictive failure asserted)"
--#ARGUMENTS  {}
--#SEVERITY   WARNING

 ::= 263169


 petTrapFanSpeedproblem TRAP-TYPE
 ENTERPRISE petEvts
 DESCRIPTION 
  "Fan Speed Problem (speed too low to meet chassis cooling specs)"

--#TYPE	"FAN Event"
--#SUMMARY    "Fan Speed Problem (speed too low to meet chassis cooling specs)"
--#ARGUMENTS  {}
--#SEVERITY   WARNING

 ::= 262402


 petTrapFanSpeedWarning TRAP-TYPE
 ENTERPRISE petEvts
 DESCRIPTION 
  "Fan speed warning (Fan speed below expected speed. Cooling still adequate)"

--#TYPE	"FAN Event"
--#SUMMARY    "Fan speed warning (Fan speed below expected speed. Cooling still adequate)"
--#ARGUMENTS  {}
--#SEVERITY   WARNING

 ::= 262400

-- **********************************************
-- *	Power Supply 				*
-- **********************************************

petTrapPowerSupplyFailureDetected TRAP-TYPE
 ENTERPRISE petEvts
 DESCRIPTION 
  "Power supply Failure detected"

--#TYPE       "Power Supply Event"
--#SUMMARY    "Power Supply failure detected"
--#ARGUMENTS  {}
--#SEVERITY   CRITICAL

 ::= 552705

petTrapPowerSupplyWarning TRAP-TYPE
 ENTERPRISE petEvts
 DESCRIPTION 
  "Power supply Warning"

--#TYPE       "Power Supply Event"
--#SUMMARY    "Power Supply Warning"
--#ARGUMENTS  {}
--#SEVERITY   WARNING

 ::= 552706

-- **********************************************
-- *	Processor 				*
-- **********************************************

-- Processor internal error
 petTrapProcessorInternalError TRAP-TYPE
 ENTERPRISE petEvts
 DESCRIPTION 
  "Processor Internal Error"

--#TYPE       "Processor Event"
--#SUMMARY    "Processor Internal Error"
--#ARGUMENTS  {}
--#SEVERITY   CRITICAL

 ::= 487168

-- Processor Thermal Trip
 petTrapProcessorThermalTrip TRAP-TYPE
 ENTERPRISE petEvts
 DESCRIPTION 
 "Processor Thermal Trip (Over Temperature Shutdown)"

--#TYPE       "Processor Event"
--#SUMMARY    "Processor Thermal Trip (Over Temperature Shutdown)"
--#ARGUMENTS  {}
--#SEVERITY   CRITICAL

 ::= 487169

-- Processor Fault Resilient Booting (FRB) 1 / Built-in self test (BIST) Error
 petTrapProcessorBistError TRAP-TYPE
 ENTERPRISE petEvts
 DESCRIPTION 
  "Processor Fault Resilient Booting (FRB) 1 / BIST (Built In Self Test) Failure"

--#TYPE       "Processor Event"
--#SUMMARY    "Processor Fault Resilient Booting (FRB) 1 / Processor BIST (Built In Self Test) Failure"
--#ARGUMENTS  {}
--#SEVERITY   CRITICAL

 ::= 487170

-- Processor Fault Resilient Booting (FRB) 2 / Hang in Power On Self Test (POST)
petTrapProcessorFRB2Failure TRAP-TYPE
 ENTERPRISE petEvts
 DESCRIPTION 
  "Processor Fault Resilient Booting (FRB) 2 / Hang in Power On Self Test (POST) Failure"

--#TYPE       "Processor Event"
--#SUMMARY    "Processor Fault Resilient Booting (FRB) 2 / Hang in Power On Self Test (POST) Failure"
--#ARGUMENTS  {}
--#SEVERITY   CRITICAL 

 ::= 487171

-- Processor Fault Resilient Booting (FRB) 3 / Processor Setup / Initialization Failure
petTrapProcessorFRB3Failure TRAP-TYPE
 ENTERPRISE petEvts
 DESCRIPTION 
  "Processor Fault Resilient Booting (FRB) 3 / Processor Setup / Initialization Failure"

--#TYPE	"Processor Event"
--#SUMMARY    "Processor Fault Resilient Booting (FRB) 3 / Processor Setup / Initialization Failure"
--#ARGUMENTS  {}
--#SEVERITY   CRITICAL

 ::= 487172

-- **********************************************
-- *			Memory			*
-- **********************************************

petTrapMemoryUncorrectableECC TRAP-TYPE
 ENTERPRISE petEvts
 DESCRIPTION 
  "Uncorrectable ECC or other uncorrectable memory error"

--#TYPE       "Memory Event"
--#SUMMARY    "Uncorrectable ECC or other uncorrectable memory error"
--#ARGUMENTS  {}
--#SEVERITY   CRITICAL

 ::= 814849


--**********************
--* Chassis Intrusion  *
--**********************

-- Chassis Intrusion
 petTrapChassisIntrusion TRAP-TYPE
 ENTERPRISE petEvts
 DESCRIPTION 
  "Chassis Intrusion - Physical Security Violation"

--#TYPE       "Chassis Intrusion Event"
--#SUMMARY    "Chassis Intrusion - Physical Security Violation"
--#ARGUMENTS  {}
--#SEVERITY   CRITICAL

 ::= 356096

-- **********************************************
-- *		Critical Interrupts		*
-- **********************************************

-- Critical Interrupt, Bus timeout error
petTrapCriticalInterruptBusTimeout TRAP-TYPE
 ENTERPRISE petEvts
 DESCRIPTION 
  "Critical Interrupt, Bus Timeout error"

--#TYPE       "Critical Interrupts Event"
--#SUMMARY    "Critical Interrupt, Bus Timeout error"
--#ARGUMENTS  {}
--#SEVERITY   CRITICAL

 ::= 1273601

-- Critical Interrupt, IO Channel Non-Maskable Interrupt
 petTrapCriticalInterruptIOChannelNMI TRAP-TYPE
 ENTERPRISE petEvts
 DESCRIPTION 
  "Critical Interrupt, IO Channel check NMI error"

--#TYPE       "Critical Interrupts Event"
--#SUMMARY    "Critical Interrupt, IO Channel check NMI error"
--#ARGUMENTS  {}
--#SEVERITY   CRITICAL

 ::= 1273602

-- Critical Interrupt, Software Non-Maskable Interrupt error
petTrapCriticalInterruptSoftwareNMI TRAP-TYPE
 ENTERPRISE petEvts
 DESCRIPTION 
  "Critical Interrupt, software NMI error"

--#TYPE       "Critical Interrupts Event"
--#SUMMARY    "Critical Interrupt, software NMI error"
--#ARGUMENTS  {}
--#SEVERITY   CRITICAL

 ::= 1273603

-- Non special-cycle parity errors
petTrapCriticalInterruptPCIPERR TRAP-TYPE
 ENTERPRISE petEvts
 DESCRIPTION 
  "Critical Interrupt, PCI PERR parity error"

--#TYPE       "Critical Interrupts Event"
--#SUMMARY    "Critical Interrupt, PCI PERR parity error"
--#ARGUMENTS  {}
--#SEVERITY   CRITICAL

 ::= 1273604

-- Special-cycle parity errors
petTrapCriticalInterruptPCISERR TRAP-TYPE
 ENTERPRISE petEvts
 DESCRIPTION 
  "Critical Interrupt, PCI SERR parity error"

--#TYPE       "Critical Interrupts Event"
--#SUMMARY    "Critical Interrupt, PCI SERR parity error"
--#ARGUMENTS  {}
--#SEVERITY   CRITICAL

 ::= 1273605

-- Bus uncorrectable error
petTrapCriticalInterruptBusUncorrect TRAP-TYPE
 ENTERPRISE petEvts
 DESCRIPTION 
  "Critical Interrupt, Bus Uncorrectable error"

--#TYPE       "Critical Interrupts Event"
--#SUMMARY    "Critical Interrupt, Bus Uncorrectable error"
--#ARGUMENTS  {}
--#SEVERITY   CRITICAL

 ::= 1273608

-- Fatal non-maskable interrupt (NMI)
petTrapCriticalInterruptFatalNMI TRAP-TYPE
 ENTERPRISE petEvts
 DESCRIPTION 
  "Critical Interrupt, Fatal NMI error"

--#TYPE       "Critical Interrupts Event"
--#SUMMARY    "Critical Interrupt, Fatal NMI error"
--#ARGUMENTS  {}
--#SEVERITY   CRITICAL

 ::= 1273609


-- **********************************************
-- *	System Firmware Progress		*
-- **********************************************

-- Power On Self Test (POST) code error
petTrapBIOSPOSTCodeError TRAP-TYPE
 ENTERPRISE petEvts
 DESCRIPTION 
  "System Firmware Progress: BIOS POST code error"

--#TYPE       "System Firmware Progress Event"
--#SUMMARY    "System Firmware Progress: BIOS POST code error"
--#ARGUMENTS  {}
--#SEVERITY   CRITICAL

 ::= 1011456


-- **********************************************
-- *	      	WatchDog			*
-- **********************************************

-- Watchdog reset event
 petTrapWatchdogReset TRAP-TYPE
 ENTERPRISE petEvts
 DESCRIPTION 
  "Watchdog Reset"

--#TYPE       "Watchdog Event"
--#SUMMARY    "Watchdog Reset"
--#ARGUMENTS  {}
--#SEVERITY   CRITICAL

 ::=  2322177

-- Watchdog power down event
 petTrapWatchdogPowerDown TRAP-TYPE
 ENTERPRISE petEvts
 DESCRIPTION 
  "Watchdog Power Down"

--#TYPE       "Watchdog Event"
--#SUMMARY    "Watchdog Power Down"
--#ARGUMENTS  {}
--#SEVERITY   CRITICAL

 ::=  2322178

-- Watchdog power cycle event
 petTrapWatchdogPowerCycle TRAP-TYPE
 ENTERPRISE petEvts
 DESCRIPTION 
  "Watchdog Power Cycle"

--#TYPE       "Watchdog Event"
--#SUMMARY    "Watchdog Power cycle"
--#ARGUMENTS  {}
--#SEVERITY   WARNING

 ::= 2322179


-- **********************************************
-- *	      	System Event Log		*
-- **********************************************

 petTrapOEMSystemBootEvent TRAP-TYPE
 ENTERPRISE petEvts
 DESCRIPTION 
  "OEM System Boot Event"

--#TYPE	"OEM System Event"
--#SUMMARY    "OEM System Boot Event"
--#ARGUMENTS  {}
--#SEVERITY   WARNING

 ::= 1208065

END
@
